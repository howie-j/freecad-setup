def main():
	load_workbenches(load='all')

	commands = Gui.listCommands()
	for command in commands:
		shortcut = Gui.Command.get(command).getShortcut()
		if ("0" <= shortcut <= "9"):
			Gui.Command.get(command).setShortcut("")
			print(command)


def load_workbenches(load='enabled'):
	'''
	Keyword arguments:
	load='enabled'  -- load only enabled workbenches
	load='all'		-- load all enabled workbenches
	'''

	workbenches = Gui.listWorkbenches()
	enabled_workbenches = list(App.ParamGet("User parameter:BaseApp/Preferences/Workbenches").GetString('Ordered').split(','))

	for wb in workbenches:
		if load == 'all' or wb in enabled_workbenches:
			Gui.activateWorkbench(wb)


main()
