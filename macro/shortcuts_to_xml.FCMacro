def main():
	load_all_workbenches()

	filename = 'shortcuts_xml.txt'
	with open(filename, 'w') as file:
		commands = Gui.listCommands()
		for command in commands:
			xml_line = f'          <FCText Name="{command}">{Gui.Command.get(command).getShortcut()}</FCText>\n'
			print(xml_line)
			file.write(xml_line)


def load_all_workbenches():
	workbenches = Gui.listWorkbenches()

	for wb in workbenches:
		Gui.activateWorkbench(wb)


main()
