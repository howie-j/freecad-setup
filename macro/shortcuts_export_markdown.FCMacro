def main():
	shortcuts = {}

	load_workbenches()
	commands = Gui.listCommands()

	for command in commands:
		shortcut = Gui.Command.get(command).getShortcut()
		if shortcut != '':
			index = command.find('_')
			wb = command[:index]
			short_command = command[index + 1:]
			icon = f'/home/howie/git/shortcuts/icons/{command}.svg'

			if not wb in shortcuts:
				shortcuts[wb] = []
			
			shortcuts[wb].append([short_command, shortcut, icon])
		
	export_list(shortcuts)


def export_list(shortcuts):
	with open("shortcuts.md", 'w') as file:
		file.write("# Shortcuts\n")

		for wb in shortcuts.keys():
			file.write(f'## {wb} \n')
			file.write("| Command | Shortcut | Icon |\n")
			file.write('| --- | --- | --- |\n')

			for command in shortcuts[wb]:
				file.write(f'| {command[0]} | `{command[1]}` | ![{command[2]}]({command[2]}) |\n')


def load_workbenches(load='enabled'):
	'''
	Keyword arguments:
	load='enabled'  -- load only enabled workbenches
	load='all'		-- load all enabled workbenches
	'''

	workbenches = Gui.listWorkbenches()
	enabled_workbenches = list(App.ParamGet("User parameter:BaseApp/Preferences/Workbenches").GetString('Ordered').split(','))

	for wb in workbenches:
		if load == 'all' or wb in enabled_workbenches:
			Gui.activateWorkbench(wb)


main()
