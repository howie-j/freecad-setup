def main():
	load_all_workbenches()

	commands = Gui.listCommands()
	for command in commands:
		if "Sketcher_" in command:
			Gui.Command.get(command).setShortcut("")
			print(command)


def load_all_workbenches():
	workbenches = Gui.listWorkbenches()

	for wb in workbenches:
		Gui.activateWorkbench(wb)


main()
